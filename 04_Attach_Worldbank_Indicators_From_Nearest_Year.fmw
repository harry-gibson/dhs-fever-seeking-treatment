FME workspace 04_Attach_Worldbank_Indicators_From_Nearest_Year.fmw

Parameters:
- DestDataset_CSV = \\map-fs1.ndph.ox.ac.uk\map_data\DHS_Automation\Processing\FeverSeekingTreatment_v2\output_v7_no_H32Z_newCIs\summary   # Destination CSV (CommaSeparatedValue) Folder
- SourceDataset_CSV2_5 = \\map-fs1.ndph.ox.ac.uk\map_data\DHS_Automation\Processing\FeverSeekingTreatment_v2\Indicators\Indicators_To_Use.csv   # Source CSV (Comma Separated Value) File(s)
- SourceDataset_CSV2 = \\map-fs1.ndph.ox.ac.uk\map_data\DHS_Automation\Processing\FeverSeekingTreatment_v2\Indicators\WorldBandIndicators_Download20170707\WDI_csv\WDIData.csv   # Source CSV (Comma Separated Value) File(s)
- SourceDataset_CSV2_7 = \\map-fs1.ndph.ox.ac.uk\map_data\DHS_Automation\Processing\FeverSeekingTreatment_v2\output_v7_no_H32Z_newCIs\FST_BySurvey_ALL.csv   # Source CSV (Comma Separated Value) File(s)
- SourceDataset_CSV2_6 = \\map-fs1.ndph.ox.ac.uk\map_data\DHS_Automation\SupportingInfo\SurveyIDs_20170711_iso_2_3.csv   # Source CSV (Comma Separated Value) File(s)
- SourceDataset_XLSXR = \\map-fs1.ndph.ox.ac.uk\map_data\GBD2017\Processing\Config_Data\National_Config_Data.xlsx   # Source Microsoft Excel File(s)

Readers:
- CSV2_1: CSV2 from $(SourceDataset_CSV2_5)
- CSV2_2: CSV2 from $(SourceDataset_CSV2)
- CSV2_3: CSV2 from $(SourceDataset_CSV2_7)
- CSV2_4: CSV2 from $(SourceDataset_CSV2_6)
- XLSXR_1: XLSXR from $(SourceDataset_XLSXR)

Writers:
- CSV_1: CSV to $(DestDataset_CSV)

Note: The raw downloaded World Bank dataset
WDIData (reader CSV2_2)
    attributes: Country Name string, Country Code string, Indicator Name string, Indicator Code string, 1960 string, 1961 string, 1962 string, 1963 string, 1964 string, 1965 string, 1966 string, 1967 string, 1968 string, 1969 string, 1970 string, 1971 string, 1972 string, 1973 string, 1974 string, 1975 string, 1976 string, 1977 string, 1978 string, 1979 string, 1980 string, 1981 string, 1982 string, 1983 string, 1984 string, 1985 string,
      1986 string, 1987 string, 1988 string, 1989 string, 1990 string, 1991 string, 1992 string, 1993 string, 1994 string, 1995 string, 1996 string, 1997 string, 1998 string, 1999 string, 2000 string, 2001 string, 2002 string, 2003 string, 2004 string, 2005 string, 2006 string, 2007 string, 2008 string, 2009 string, 2010 string, 2011 string, 2012 string, 2013 string, 2014 string, 2015 string,
      2016 string, col61 string
    -> FeatureMerger_2 [REQUESTOR]
Note: Simple listing of which indicators are required
Indicators_To_Use (reader CSV2_1)
    attributes: Indicator Name string, Indicator Code string, Short Name string
    -> FeatureMerger_2 [SUPPLIER]
FeatureMerger_2
    MERGE_TYPE = Attributes Only
    IGNORE_NULLS = No
    PROCESS_DUPS = No
    JOIN_KEYS = @Value(Indicator Code) @Value(Indicator Code) AUTO
    ATTR_ACCUM_MODE = Merge Supplier
    REJECT_NULL_MISSING_KEYS = No
    SUPPLIERS_FIRST = Yes
    ATTR_CONFLICT_RES = Use Requestor
    MERGED -> AttributeRenamer
AttributeRenamer
    ATTR_TABLE = RENAME_SET_DEFAULT Short Name > indicatorname
    -> AttributeRemover
AttributeRemover
    REMOVE_ATTRS = Country Name,col61,Indicator Name,Indicator Code
    -> AttributeExploder
Note: Split into one feature per attribute i.e. a single year per feature / (normalise), then tidy up
AttributeExploder
    ATTR_VALUE_LABEL = _attr_value
    KEEP_ATTRIBUTES = Yes
    KEEP_GEOMETRY = No
    ATTR_NAME_LABEL = _attr_name
    EXPLODING_TYPE = Features
    -> AttributeKeeper
AttributeKeeper
    KEEP_ATTRS = _attr_name,_attr_value,indicatorname,Country Code
    -> Tester_3
Tester_3
    BOOL_OP = AND
    TEST_MODE = Automatic
    TEST_CLAUSE:
      TEST _attr_value NOT_ATTRIBUTE_IS_EMPTY ""
      TEST _attr_value NOT_ATTRIBUTE_VALUE_NULL ""
    TEST_DESCRIPTION = ""
    PASSED -> FeatureMerger [SUPPLIER]
Note: This workbench reads in the combined national summary data produced from the fever treatment extraction workbench. One row = one survey (country/year). / It then attaches to each row each worldbank indicator value for the corresponding year and country to the survey. / The catch is that there isn't necessarily a worldbank indicator value for the relevant country in the survey year, and indeed there isn't the same availability for each indicator in a given country / year. / So instead we identify for each combination of survey (year), country, and indicator, the nearest year to the survey year that there is a worldbank value for, and use that (and record which year we used for each indicator). / We output the original data, with columns added for each required indicator and the year used. The original data columns are reformatted to suit the schema needed by the downstream modelling.
Note: National-level result from the main FST workbench
FST_BySurvey_ALL (reader CSV2_3)
    attributes: SurveyName string, SurveyId string, DHS_CountryCode string, SurveyYear string, SurveyType string, SurveyStatus string, CountryName string, SurveyYearLabel string, young_child_wt.nationalcount string, had_fever_wt.nationalcount string, public_treat_wt.nationalcount string, any_treat_wt.nationalcount string, had_fever_wt.nationalprop string, fever_public_treat_wt.nationalprop string, fever_any_treat_wt.nationalprop string, fever_any_treat_wt_stderr string, fever_public_treat_wt_stderr string, fever_any_treat_wt_stdev string, fever_public_treat_wt_stdev string, fever_any_treat_wt_mean string, fever_public_treat_wt_mean string, fever_public_treat_wt.nationalprop_LCI_GLM string, fever_public_treat_wt.nationalprop_UCI_GLM string, fever_any_treat_wt.nationalprop_LCI_GLM string, fever_any_treat_wt.nationalprop_UCI_GLM string, fever_public_treat_wt.nationalprop_LCI_SVY string, fever_public_treat_wt.nationalprop_UCI_SVY string, fever_any_treat_wt.nationalprop_LCI_SVY string, fever_any_treat_wt.nationalprop_UCI_SVY string
    -> FeatureMerger_4 [REQUESTOR]
Note: A copy of the DHS Survey catalogue (retrieved from their API) to which an ISO_3 country code column has been manually added
SurveyIDs_20170711_iso_2_3 (reader CSV2_4)
    attributes: SurveyId string, DHS_CountryCode string, ISO_2 string, ISO_3 string, SurveyYear string, SurveyType string, SurveyStatus string, CountryName string, SurveyYearLabel string, SurveyNum string, IndicatorData string, RegionName string, SubregionName string, PublicationDate string, ReleaseDate string, SurveyCharacteristicIds string, Footnotes string, FieldworkStart string, FieldworkEnd string, ImplementingOrg string, NumberOfSamplePoints string, NumberofHouseholds string, UniverseOfWomen string, NumberOfWomen string, MinAgeWomen string, MaxAgeWomen string, UniverseOfMen string, NumberOfMen string, MinAgeMen string, MaxAgeMen string,
      NumberOfFacilities string
    -> FeatureMerger_4 [SUPPLIER]
Note: Attach ISO3 to the results so we can match to the ISO3-referenced World Bank data; also the "official" year of the survey
FeatureMerger_4
    MERGE_TYPE = Attributes Only
    IGNORE_NULLS = No
    PROCESS_DUPS = No
    JOIN_KEYS = @Value(SurveyId) @Value(SurveyNum) AUTO
    ATTR_ACCUM_MODE = Merge Supplier
    REJECT_NULL_MISSING_KEYS = No
    SUPPLIERS_FIRST = No
    ATTR_CONFLICT_RES = Use Supplier
    MERGED -> AttributeKeeper_3
    MERGED -> FeatureMerger_5 [REQUESTOR]
Note: Survey year can be a text value like 2007-08 so clean it
AttributeKeeper_3
    KEEP_ATTRS = SurveyYear,SurveyId,ISO_3
    -> StringSearcher
StringSearcher
    STRING_TO_SEARCH = @Value(SurveyYear)
    MATCHED_PARTS_ATTR = _matched_parts
    CASE = no
    MATCHED_RESULT_ATTR = _year_Clean
    REGEXP = ^\d+
    MATCHED -> FeatureMerger [REQUESTOR]
    NOT_MATCHED -> StringSearcher_NotMatched
StringSearcher_NotMatched: Inspector
Note: For each survey, join all indicator / year pairs for that country onto a list, and tidy up
FeatureMerger
    MERGE_TYPE = Attributes Only
    IGNORE_NULLS = Yes
    PROCESS_DUPS = Yes
    GEOM_TYPE = Build Polygons
    JOIN_KEYS = @Value(ISO_3) @Value(Country Code) AUTO
    ATTR_ACCUM_MODE = Merge Supplier
    SUPPLIERS_FIRST = No
    ATTR_CONFLICT_RES = Use Requestor
    LIST_NAME = _mergedIndicators
    MERGED -> AttributeRemover_2
    NOT_MERGED -> Indicator_KVP_Unknown_Country
Indicator_KVP_Unknown_Country: Inspector
AttributeRemover_2
    REMOVE_ATTRS = _attr_name,_attr_value,DHS,indicatorname
    -> FeatureMerger_Merged
    -> ListExploder
Note: Explode that list to get a feature for each possible match
ListExploder
    ATTR_ACCUM_MODE = Merge Incoming List
    INDEX_ATTR = _element_index
    ATTR_CONFLICT_RES = Use Original
    LIST_ATTR = _mergedIndicators{}
    LIST_FOUND -> AttributeCreator_3
Note: Having exploded the list we now have one feature for each survey / indicator / year combination. / Calculate for each of these how different the indicator year is from the survey year (if at all)
AttributeCreator_3
    ATTR_LIST = _indicatorOffset,"FME_CONDITIONAL:DEFAULT_VALUE'9999'BOOL_OP;OR;COMPOSITE_TEST;<Unused>;TEST @Value(_attr_name) MATCHES_REGEX ^\d+$'@Evaluate(@abs(@Value(_year_Clean)-@Value(_attr_name)))'FME_NUM_CONDITIONS2___"
    -> Tester_2
Note: Drop anything that wasn't a year value
Tester_2
    BOOL_OP = OR
    TEST_MODE = Automatic
    TEST_CLAUSE = TEST @Value(_indicatorOffset) != 9999
    TEST_DESCRIPTION = ""
    PASSED -> Sorter
Note: For each survey and indicator, take the year that is closest to the survey year, by sorting then taking the first (c.f. SELECT / GROUP BY / ORDER BY / LIMIT 1)
Sorter
    SORT_PARM = SurveyId NUMERIC ASCENDING indicatorname ALPHA ASCENDING _indicatorOffset NUMERIC ASCENDING
    SORTED -> Sampler
Sampler
    RATE = 1
    GROUP_BY = SurveyId indicatorname
    SAMPLE_TYPE_LONG = First N Features
    SAMPLED -> AttributeRenamer_3
AttributeRenamer_3
    ATTR_LIST = _attr_name,_IndicatorYearUsed,
    -> BulkAttributeRenamer
    -> Sampler_Sampled
Note: Use BulkAttributeRenamer to rename "_attr_value", (the value of whatever this particular indicator is) to the name of the indicator itself. / This use of the bulkattributerenamer is sneaky: it renames one attribute to a name that is given in the value of another attribute. / This means that the workspace doesn't know what the attribute name will be coming out, as this can't be known until runtime, so the writer attributes have to be defined either manually (as done here) or by building a schema-definition feature with further list-munging
BulkAttributeRenamer
    ATTRCHOICE = Selected Attributes
    PATTERN_ACTION_DISP = String Replace
    ATTRLIST = _attr_value
    REPLACE_STR = @Value(indicatorname)
    CASE_DISP = yes
    REPLACE_PATTERN = _attr_value
    -> BulkAttributeRenamer_2
BulkAttributeRenamer_2
    ATTRCHOICE = Selected Attributes
    PATTERN_ACTION_DISP = Add String Prefix
    ATTRLIST = _IndicatorYearUsed
    REPLACE_STR = @Value(indicatorname)
    -> AttributeRemover_3
    -> BulkAttributeRenamer_2_Output
BulkAttributeRenamer_2_Output: Inspector [off]
AttributeRemover_3
    REMOVE_ATTRS = _attr_value,_element_index,indicatorname,ISO3,year
    -> BulkAttributeRenamer_Output
    -> FeatureMerger_3 [SUPPLIER]
BulkAttributeRenamer_Output: Inspector [off]
Sampler_Sampled: Inspector [off]
FeatureMerger_Merged: Inspector
National_Config_Data (reader XLSXR_1)
    attributes: MAP_Country_Name char(37), Country_Exists_From char(11), ISO2 char(3), ISO3 char(4), GAUL_Code number(6,0), Geometry_ID string, WHO_Region char(6), WHO_Subregion char(7), World_Bank_Region char(5), World_Bank_Region_Name char(29), World_Bank_Country_Name char(31), IHME_location_id number(4,0), IHME_Loc_ID char(4), IHME_Local_ID char(4), IHME_Location_Name_Short char(18), IHME_Location_ASCII_Name char(33), IHME_Super_Region_ID number(4,0), IHME_Super_Region_Name char(49), IHME_Region_ID number(4,0), IHME_Region_Name char(29), IHME_Process_Subnationally char(4), MAP_Pv_Relapse_Zone number(3,0), MAP_Include char(2), MAP_Pv_Model_Method char(13), MAP_Pf_Model_Method char(13), MAP_Pv_Preferred_Output char(4), MAP_Pf_Preferred_Output char(4), Gold_Standard_Date char(5), Silver_Standard_Date char(5), WHO_Current_Phase char(26),
      WHO_Elimination_Date char(5), WHO_Elimination_Phase_Date char(5), WHO_Pre_Elimination_Phase_Date char(5), WHO_Pv_Free_Date char(5), WHO_Pf_Free_Date char(5)
    -> AttributeManager_2
AttributeManager_2
    ATTR_TABLE:
      RENAME_SET_VALUE ISO3 > ISO_3
      RENAME_SET_VALUE WHO_Region > WHO
      RENAME_SET_VALUE WHO_Subregion > WHO_Sub
    -> FeatureMerger_5 [SUPPLIER]
FeatureMerger_5
    MERGE_TYPE = Attributes Only
    IGNORE_NULLS = No
    PROCESS_DUPS = No
    JOIN_KEYS = @Value(ISO_3) @Value(ISO_3) AUTO
    ATTR_ACCUM_MODE = Merge Supplier
    REJECT_NULL_MISSING_KEYS = No
    SUPPLIERS_FIRST = No
    ATTR_CONFLICT_RES = Use Requestor
    MERGED -> Counter
    UNMERGED_REQUESTOR -> Counter
    <REJECTED> -> FeatureMerger_5__Rejected_
Counter
    DOMAIN = counter
    SCOPE = Global
    START = 1
    CNT_ATTR = _count
    -> AttributeManager_3
AttributeManager_3
    ATTR_TABLE:
      SET_TO Check = @Value(ISO_3)_@Value(WHO_Sub)_@Value(SurveyYear)
      SET_TO ID = DHS_@Value(_count)
      REMOVE _count
    -> FeatureMerger_3 [REQUESTOR]
Note: Attach all that nonsense back onto the original incoming features. / Allow Process Duplicate Suppliers so that the incoming name / value pair attributes all accumulate onto the source survey row feature - there will be one for each indicator
FeatureMerger_3
    MERGE_TYPE = Attributes Only
    IGNORE_NULLS = No
    PROCESS_DUPS = Yes
    GEOM_TYPE = Build Polygons
    JOIN_KEYS = @Value(SurveyId) @Value(SurveyId) AUTO
    ATTR_ACCUM_MODE = Merge Supplier
    SUPPLIERS_FIRST = No
    ATTR_CONFLICT_RES = Use Requestor
    MERGED -> FeatureMerger_3_Merged
    MERGED -> AttributeManager
FeatureMerger_3_Merged: Inspector
AttributeManager
    ATTR_TABLE:
      RENAME_SET_VALUE CountryName > Country
      RENAME_SET_VALUE DHS_CountryCode > Country_DHScode
      RENAME_SET_VALUE ISO_3 > Country_ISO3Code
      RENAME_SET_VALUE SurveyYear > Year
      REMOVE SurveyId
      REMOVE SurveyStatus
      REMOVE SurveyYearLabel
      RENAME_SET_VALUE young_child_wt.nationalcount > TotalChildren
      RENAME_SET_VALUE had_fever_wt.nationalcount > TotalFevers
      RENAME_SET_VALUE public_treat_wt.nationalcount > TotalHMISTreat
      RENAME_SET_VALUE any_treat_wt.nationalcount > TotalAnyTreat
      RENAME_SET_VALUE had_fever_wt.nationalprop > FeverProp
      RENAME_SET_VALUE fever_public_treat_wt.nationalprop > HMIS_treat
      RENAME_SET_VALUE fever_public_treat_wt_stdev > sdHMIS
      RENAME_SET_VALUE fever_public_treat_wt_mean > meanHMIS
      RENAME_SET_VALUE fever_public_treat_wt_stderr > seHMIS
      RENAME_SET_VALUE fever_public_treat_wt.nationalprop_LCI_GLM > HMIS_treat_low_GLM
      RENAME_SET_VALUE fever_public_treat_wt.nationalprop_UCI_GLM > HMIS_treat_high_GLM
      RENAME_SET_VALUE fever_public_treat_wt.nationalprop_LCI_SVY > HMIS_treat_low_SVY
      RENAME_SET_VALUE fever_public_treat_wt.nationalprop_UCI_SVY > HMIS_treat_high_SVY
      RENAME_SET_VALUE fever_any_treat_wt.nationalprop > Any_treat
      RENAME_SET_VALUE fever_any_treat_wt_stdev > sdAny
      RENAME_SET_VALUE fever_any_treat_wt_mean > meanAny
      RENAME_SET_VALUE fever_any_treat_wt_stderr > seAny
      RENAME_SET_VALUE fever_any_treat_wt.nationalprop_LCI_GLM > Any_treat_low_GLM
      RENAME_SET_VALUE fever_any_treat_wt.nationalprop_UCI_GLM > Any_treat_high_GLM
      RENAME_SET_VALUE fever_any_treat_wt.nationalprop_LCI_SVY > Any_treat_low_SVY
      RENAME_SET_VALUE fever_any_treat_wt.nationalprop_UCI_SVY > Any_treat_high_SVY
      RENAME_SET_VALUE SurveyNum > DHSSurveyNum
    -> NationalSurveyResults_Weighted_With_UpdatedIndicators (writer CSV_1)
Note: The attributes that are added in this WB (not from the incoming FST) will need to be defined manually on here due to the BulkAttributeRenamer. For each "shortname" specified in the Indicators To Use file there will be one corresponding attribute on here, plus another with the suffix _IndicatorYearUsed
NationalSurveyResults_Weighted_With_UpdatedIndicators (writer CSV_1)
    attributes: SurveyType text, Country text, Country_DHScode text, Country_ISO3Code text, WHO text, WHO_Sub text, Year text, Check text, ID text, SurveyName text, DHSSurveyNum text, TotalChildren text, TotalFevers text, TotalHMISTreat text, TotalAnyTreat text, FeverProp text, HMIS_treat text, sdHMIS text, meanHMIS text, seHMIS text, HMIS_treat_low_GLM text, HMIS_treat_high_GLM text, HMIS_treat_low_SVY text, HMIS_treat_high_SVY text, Any_treat text, sdAny text, meanAny text, seAny text, Any_treat_low_GLM text, Any_treat_high_GLM text,
      Any_treat_low_SVY text, Any_treat_high_SVY text, Electricity char(20), Electricity_IndicatorYearUsed auto, GDP auto, GDP_IndicatorYearUsed auto, GDPGrowth auto, GDPGrowth_IndicatorYearUsed auto, GDPpercap auto, GDPpercap_IndicatorYearUsed auto, GNIpercap auto, GNIpercap_IndicatorYearUsed auto, HealthExpercap auto, HealthExpercap_IndicatorYearUsed auto, HealthExPub auto, HealthExPub_IndicatorYearUsed auto, HealthExTotal auto, HealthExTotal_IndicatorYearUsed auto, Literacy auto, Literacy_IndicatorYearUsed auto, PregWomenCare auto, PregWomenCare_IndicatorYearUsed auto, PrimaryComplete auto, PrimaryComplete_IndicatorYearUsed auto, RuralPop auto, RuralPop_IndicatorYearUsed auto, UrbanPop auto, UrbanPop_IndicatorYearUsed auto, CommHlthWrkrs auto, CommHlthWrkrs_IndicatorYearUsed auto,
      DPT auto, DPT_IndicatorYearUsed auto, NurseMidwives auto, NurseMidwives_IndicatorYearUsed auto
FeatureMerger_5__Rejected_: Inspector
