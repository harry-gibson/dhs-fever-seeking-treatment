FME workspace _devChildCIs.fmw

Parameters:
- SourceDataset_CSV2_3 = \\map-fs1.ndph.ox.ac.uk\map_data\DHS_Automation\Processing\FeverSeekingTreatment_v2\output_v6_no_H32Z_withCIs\FST_ByChild_ALL.csv   # Source CSV (Comma Separated Value) File(s)
- SourceDataset_CSV2 = \\map-fs1.ndph.ox.ac.uk\map_data\DHS_Automation\Processing\FeverSeekingTreatment_v2\output_v6_no_H32Z_withCIs\FST_BySurvey_ALL.csv   # Source CSV (Comma Separated Value) File(s)
- DestDataset_CSV2 = \\map-fs1.ndph.ox.ac.uk\map_data\DHS_Automation\Processing\FeverSeekingTreatment_v2\output_v7_no_H32Z_newCIs   # Destination CSV (Comma Separated Value) Folder

Readers:
- CSV2_1: CSV2 from $(SourceDataset_CSV2_3)
- CSV2_2: CSV2 from $(SourceDataset_CSV2)

Writers:
- CSV2_3: CSV2 to $(DestDataset_CSV2)

Note: Load an earlier copy of the national output file to which we might want to attach a different set of CIs
CSV (reader CSV2_2)
    attributes: SurveyName string, SurveyId string, DHS_CountryCode string, SurveyYear string, SurveyType string, SurveyStatus string, CountryName string, SurveyYearLabel string, young_child_wt.nationalcount string, had_fever_wt.nationalcount string, public_treat_wt.nationalcount string, any_treat_wt.nationalcount string, had_fever_wt.nationalprop string, fever_public_treat_wt.nationalprop string, fever_any_treat_wt.nationalprop string, fever_public_treat_wt.nationalprop_LCI_CL string, fever_public_treat_wt.nationalprop_UCI_CL string, fever_any_treat_wt.nationalprop_LCI_CL string, fever_any_treat_wt.nationalprop_UCI_CL string, fever_public_treat_wt.nationalprop_LCI_BS string, fever_public_treat_wt.nationalprop_UCI_BS string, fever_any_treat_wt.nationalprop_LCI_BS string, fever_any_treat_wt.nationalprop_UCI_BS string, fever_public_treat_wt.nationalprop_LCI_GLM string, fever_public_treat_wt.nationalprop_UCI_GLM string, fever_any_treat_wt.nationalprop_LCI_GLM string, fever_any_treat_wt.nationalprop_UCI_GLM string, fever_any_treat_wt_stderr string, fever_public_treat_wt_stderr string, fever_any_treat_wt_stdev string,
      fever_public_treat_wt_stdev string, fever_any_treat_wt_mean string, fever_public_treat_wt_mean string
    -> AttributeManager
Note: Tidy up old CIs
Note: Allows development / checking of the RCaller code based on child data stored in a CSV (from a previous run of the main FST extraction workbench). / Also allows running of the R code to attach child-derived CIs to the national data based on CSVs from a previous run of the main WB, without having to re-run it (which takes a couple of hours)
AttributeManager
    ATTR_TABLE:
      REMOVE fever_public_treat_wt.nationalprop_LCI_CL
      REMOVE fever_public_treat_wt.nationalprop_UCI_CL
      REMOVE fever_any_treat_wt.nationalprop_LCI_CL
      REMOVE fever_any_treat_wt.nationalprop_UCI_CL
      REMOVE fever_public_treat_wt.nationalprop_LCI_BS
      REMOVE fever_public_treat_wt.nationalprop_UCI_BS
      REMOVE fever_any_treat_wt.nationalprop_LCI_BS
      REMOVE fever_any_treat_wt.nationalprop_UCI_BS
    -> FeatureMerger [REQUESTOR]
Note: Load child-level data for one or for all surveys
CSV (reader CSV2_1)
    attributes: SurveyName string, SurveyId string, DHS_CountryCode string, SurveyYear string, SurveyType string, SurveyStatus string, CountryName string, SurveyYearLabel string, child_num string, woman_id string, clusterid string, latitude string, longitude string, region string, urban_rural string, wealth_quint string, young_child_wt string, had_fever_wt string, public_treat_wt string, any_treat_wt string
    -> Tester_9
Tester_9
    TEST_DESCRIPTION = ""
    TEST_MODE = Automatic
    BOOL_OP = OR
    TEST_CLAUSE = TEST @Value(had_fever_wt) > 0
    PASSED -> AttributeManager_CHILD_2
Note: Change the attributes of the CSV-saved child data to match what they would have had in the main workbench at the point they entered the RCaller there - so that we can just copy and paste the RCaller from this WB to that one
AttributeManager_CHILD_2
    ATTR_TABLE:
      REMOVE child_num
      REMOVE woman_id
      REMOVE clusterid
      REMOVE latitude
      REMOVE longitude
      REMOVE region
      SET_TO had_fever = FME_CONDITIONAL:DEFAULT_VALUE'0'BOOL_OP;OR;COMPOSITE_TEST;<Unused>;TEST @Value(had_fever_wt) > 0'1'FME_NUM_CONDITIONS2___
      SET_TO public_treat = FME_CONDITIONAL:DEFAULT_VALUE'0'BOOL_OP;OR;COMPOSITE_TEST;<Unused>;TEST @Value(public_treat_wt) > 0'1'FME_NUM_CONDITIONS2___
      SET_TO any_treat = FME_CONDITIONAL:DEFAULT_VALUE'0'BOOL_OP;OR;COMPOSITE_TEST;<Unused>;TEST @Value(any_treat_wt) > 0'1'FME_NUM_CONDITIONS2___
      REMOVE had_fever_wt
      REMOVE any_treat_wt
      REMOVE public_treat_wt
      REMOVE urban_rural
      REMOVE wealth_quint
      REMOVE SurveyName
      RENAME_SET_VALUE SurveyId > surveyid
      REMOVE DHS_CountryCode
      REMOVE SurveyYear
      REMOVE SurveyType
      REMOVE SurveyStatus
      REMOVE CountryName
      REMOVE SurveyYearLabel
    -> RCaller_3 [childraw]
RCaller_3
    QUERY_DEF:
      Output,library(plyr)
      # these next two libraries are required for running copies of the function (one per survey) in parallel
      # on windows - there are other choices than doParallel esp on linux
      library(foreach)
      library(doParallel)

      # function to create 95% confidence intervals for the national proportions based on the raw
      # child level had-treatment data. Input data should contain only children who had fever.
      createCIs <- function(dfInput){
        library(survey)
        # create GLMs for the relationship between the response column and the predictor "1"
        pubmod <- glm(public_treat~1, data=dfInput, family=quasibinomial(), weights=young_child_wt)
        anymod <- glm(any_treat~1, data=dfInput, family=quasibinomial(), weights=young_child_wt)

        dfOut <- tryCatch({
            meanpub <- plogis(coef(pubmod))
            confpub <- plogis(confint(pubmod))
            meanany <- plogis(coef(anymod))
            confany <- plogis(confint(anymod))

            # create a survey design object to use the survey package for estimating CIs
            SVY <- svydesign(id=~1, weights=~young_child_wt, data=dfInput)
            coefpub <- svymean(~public_treat, SVY, deff=FALSE, na.rm=TRUE)
            coefany <- svymean(~any_treat, SVY, deff=FALSE, na.rm=TRUE)
            svyconfpub <- confint(coefpub)
            svyconfany <- confint(coefany)

            data.frame(glm_mean_public=meanpub, glm_lci_public=confpub["2.5 %"], glm_uci_public=confpub["97.5 %"],
              glm_mean_any=meanany, glm_lci_any=confany["2.5 %"], glm_uci_any=confany["97.5 %"],
              svy_lci_public=svyconfpub[1], svy_uci_public=svyconfpub[2],
              svy_lci_any=svyconfany[1], svy_uci_any=svyconfany[2])
        },
        error=function(cond){
            return (data.frame(glm_mean_public=-9999, glm_lci_public=-9999, glm_uci_public=-9999,
              glm_mean_any=-9999, glm_lci_any=-9999, glm_uci_any=-9999))
        },
        warning=function(cond){return(NULL)}
        )
        return (dfOut)
      }

      # how many cores to use - my machine has 12, adjust to suit
      workers <- makeCluster(10)
      registerDoParallel(workers)

      # output a dataframe containing one row (=fme feature) for each input survey, by calling the
      # createCIs function for each survey's data in turn (like GROUP BY)
      # Use parallel functionality to ensure it runs in a decent amount of time. On a single core
      # with all 200+ surveys it takes 10 minutes+ and this times out in FME making the translation fail.
      fmeOutput <- ddply(childraw, "surveyid", createCIs, .parallel = TRUE)
      ,surveyid glm_mean_public glm_lci_public glm_uci_public glm_mean_any glm_lci_any glm_uci_any svy_lci_public svy_uci_public svy_lci_any svy_uci_any
    OUTPUT_SCHEMA = surveyid glm_mean_public glm_lci_public glm_uci_public glm_mean_any glm_lci_any glm_uci_any svy_lci_public svy_uci_public svy_lci_any svy_uci_any
    TABLE_DEF = childraw,surveyid,text,any_treat,integer,had_fever,integer,young_child_wt,"real(20,10)",public_treat,integer
    -> RCaller_2_Output
    -> AttributeManager_2
Note: Make any changes necessary for updating the national file - or disable this if we're just fiddling about with the R code
AttributeManager_2
    ATTR_TABLE:
      RENAME_SET_VALUE surveyid > SurveyId
      REMOVE glm_mean_public
      REMOVE glm_lci_public
      REMOVE glm_uci_public
      REMOVE glm_mean_any
      REMOVE glm_lci_any
      REMOVE glm_uci_any
      RENAME_SET_VALUE svy_lci_public > fever_public_treat_wt.nationalprop_LCI_SVY
      RENAME_SET_VALUE svy_uci_public > fever_public_treat_wt.nationalprop_UCI_SVY
      RENAME_SET_VALUE svy_lci_any > fever_any_treat_wt.nationalprop_LCI_SVY
      RENAME_SET_VALUE svy_uci_any > fever_any_treat_wt.nationalprop_UCI_SVY
    -> FeatureMerger [SUPPLIER]
FeatureMerger
    ATTR_ACCUM_MODE = Merge Supplier
    JOIN_KEYS = @Value(SurveyId) @Value(SurveyId) AUTO
    IGNORE_NULLS = No
    SUPPLIERS_FIRST = No
    REJECT_NULL_MISSING_KEYS = No
    PROCESS_DUPS = No
    ATTR_CONFLICT_RES = Use Requestor
    MERGE_TYPE = Attributes Only
    MERGED -> FST_BySurvey_All (writer CSV2_3)
    MERGED -> AttributeCreator
AttributeCreator
    ATTR_TABLE = SET_TO _OutFN = FST_BySurvey_@Value(SurveyId)_@Value(SurveyName)
    -> CSV00 (writer CSV2_3)
Note: Ensure we write to a new folder, don't overwrite the input!
CSV00 (writer CSV2_3)
    attributes: SurveyName string, SurveyId string, DHS_CountryCode string, SurveyYear string, SurveyType string, SurveyStatus string, CountryName string, SurveyYearLabel string, young_child_wt.nationalcount string, had_fever_wt.nationalcount string, public_treat_wt.nationalcount string, any_treat_wt.nationalcount string, had_fever_wt.nationalprop string, fever_public_treat_wt.nationalprop string, fever_any_treat_wt.nationalprop string, fever_public_treat_wt.nationalprop_LCI_GLM string, fever_public_treat_wt.nationalprop_UCI_GLM string, fever_any_treat_wt.nationalprop_LCI_GLM string, fever_any_treat_wt.nationalprop_UCI_GLM string, fever_public_treat_wt.nationalprop_LCI_SVY string, fever_public_treat_wt.nationalprop_UCI_SVY string, fever_any_treat_wt.nationalprop_LCI_SVY string, fever_any_treat_wt.nationalprop_UCI_SVY string, fever_any_treat_wt_stderr string, fever_public_treat_wt_stderr string, fever_any_treat_wt_stdev string, fever_public_treat_wt_stdev string, fever_any_treat_wt_mean string, fever_public_treat_wt_mean string
FST_BySurvey_All (writer CSV2_3)
    attributes: SurveyName string, SurveyId string, DHS_CountryCode string, SurveyYear string, SurveyType string, SurveyStatus string, CountryName string, SurveyYearLabel string, young_child_wt.nationalcount string, had_fever_wt.nationalcount string, public_treat_wt.nationalcount string, any_treat_wt.nationalcount string, had_fever_wt.nationalprop string, fever_public_treat_wt.nationalprop string, fever_any_treat_wt.nationalprop string, fever_public_treat_wt.nationalprop_LCI_GLM string, fever_public_treat_wt.nationalprop_UCI_GLM string, fever_any_treat_wt.nationalprop_LCI_GLM string, fever_any_treat_wt.nationalprop_UCI_GLM string, fever_public_treat_wt.nationalprop_LCI_SVY string, fever_public_treat_wt.nationalprop_UCI_SVY string, fever_any_treat_wt.nationalprop_LCI_SVY string, fever_any_treat_wt.nationalprop_UCI_SVY string, fever_any_treat_wt_stderr string, fever_public_treat_wt_stderr string, fever_any_treat_wt_stdev string, fever_public_treat_wt_stdev string, fever_any_treat_wt_mean string, fever_public_treat_wt_mean string
RCaller_2_Output: Inspector
