FME workspace 03_Attach_Region_Names.fmw

Parameters:
- DestDataset_CSV2 = C:\Users\zool1301.NDPH\Documents\Code_General\FeverSeekingTreatment_v2\Intermediary_Outputs   # Destination CSV (Comma Separated Value) Folder
- SourceDataset_CSV2_2 = C:\Users\zool1301.NDPH\Documents\Code_General\FeverSeekingTreatment_v2\Intermediary_Outputs\FST_ByRegionALL.csv   # Source CSV (Comma Separated Value) File(s)
- FEATURE_TYPES_2 =

Readers:
- CSV2_3: CSV2 from $(SourceDataset_CSV2_2)

Writers:
- CSV2_2: CSV2 to $(DestDataset_CSV2)

CSV (reader CSV2_3)
    attributes: SurveyName string, SurveyId string, DHS_CountryCode string, SurveyYear string, SurveyType string, SurveyStatus string, CountryName string, SurveyYearLabel string, region string, young_child_wt.regioncount string, had_fever_wt.regioncount string, public_treat_wt.regioncount string, any_treat_wt.regioncount string, had_fever_wt.regionprop string, fever_public_treat_wt.regionprop string, fever_public_treat_wt.regionprop_LCI_SVY string, fever_public_treat_wt.regionprop_UCI_SVY string, fever_any_treat_wt.regionprop string, fever_any_treat_wt.regionprop_LCI_SVY string, fever_any_treat_wt.regionprop_UCI_SVY string
    -> AttributeCreator
AttributeCreator
    ATTR_TABLE = SET_TO _reg_col_name = HV024
    -> DatabaseJoiner
DatabaseJoiner
    ADDED_FIELDS = value_desc
    ATTR_ACCUM_MODE = Merge Joined
    ATTR_CONFLICT_RES = Use Original
    CACHE_SIZE = 5000
    DATASET = DHS Data Readonly
    FORMAT = POSTGRES
    JOIN_KEYS = SurveyId surveyid region value _reg_col_name col_name
    MATCH_RULE_DISPLAY = Must Match Zero or One (1:0..1)
    POSTGRES_NAMED_CONNECTION = DHS Data Readonly
    POSTGRES_QUERY_FEATURE_TYPES_FOR_MERGE_FILTERS = Yes
    POSTGRES_READ_TIME_WITH_TIMEZONE = Yes
    PREFETCH_EXHAUSTIVE = Yes
    TABLE = dhs_survey_specs.dhs_value_descs
    JOINED -> AttributeManager
    <REJECTED> -> DatabaseJoiner__Rejected_
AttributeManager
    ATTR_TABLE:
      REMOVE _reg_col_name
      RENAME_SET_VALUE value_desc > DHS_Region_Name
      REMOVE fme_feature_type
      REMOVE _matched_records
    -> DatabaseJoiner_Joined
    -> FST_ByRegion_ALL_with_CI_and_region_name (writer CSV2_2)
DatabaseJoiner_Joined: Inspector
FST_ByRegion_ALL_with_CI_and_region_name (writer CSV2_2)
    attributes: SurveyName string, SurveyId string, DHS_CountryCode string, SurveyYear string, SurveyType string, SurveyStatus string, CountryName string, SurveyYearLabel string, region string, DHS_Region_Name string, young_child_wt.regioncount string, had_fever_wt.regioncount string, public_treat_wt.regioncount string, any_treat_wt.regioncount string, had_fever_wt.regionprop string, fever_public_treat_wt.regionprop string, fever_public_treat_wt.regionprop_LCI_SVY string, fever_public_treat_wt.regionprop_UCI_SVY string, fever_any_treat_wt.regionprop string, fever_any_treat_wt.regionprop_LCI_SVY string, fever_any_treat_wt.regionprop_UCI_SVY string
DatabaseJoiner__Rejected_: Inspector
