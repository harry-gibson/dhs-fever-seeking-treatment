FME workspace Fever_Seeking_Treatment_From_DB_with_CIs.fmw

Parameters:
- SourceDataset_CSV2 = Z:\DHS_Automation\Processing\FeverSeekingTreatment_v2\code\sample_data\input\fst_sample_input.csv   # Source CSV (Comma Separated Value) File(s)
- DestDataset_CSV2 = Z:\DHS_Automation\Processing\FeverSeekingTreatment_v2\code\sample_data\output_with_ci   # Destination CSV (Comma Separated Value) Folder
- SourceDataset_CSV2_7 = http://api.dhsprogram.com/rest/dhs/surveys?f=csv   # Source CSV (Comma Separated Value) File(s)

Readers:
- CSV2_1: CSV2 from $(SourceDataset_CSV2_7)
- CSV2_2: CSV2 from $(SourceDataset_CSV2)

Writers:
- CSV2_3: CSV2 to $(DestDataset_CSV2)

CSV (reader CSV2_2)
    attributes: FileCode string, RecordName string, RecordLabel string, Name string, Label string, surveyid string, NewPublicTreat string, NewAnyTreat string
    -> AttributeRenamer
Tester_8
    BOOL_OP = OR
    TEST_DESCRIPTION = ""
    TEST_CLAUSE = TEST @Value(surveyid) = 324
    TEST_MODE = Automatic
    PASSED -> AttributeRenamer
AttributeRenamer
    ATTR_TABLE:
      RENAME_SET_DEFAULT NewAnyTreat > _any_treat
      RENAME_SET_DEFAULT NewPublicTreat > _public_treat
    -> Sampler
    -> AttributeKeeper_2
Sampler
    GROUP_BY = surveyid
    SAMPLE_TYPE_LONG = First N Features
    RATE = 1
    SAMPLE_MODE = No
    SAMPLED -> AttributeKeeper
AttributeKeeper
    KEEP_ATTRS = surveyid
    -> FeatureMerger [REQUESTOR]
    -> FeatureMerger_2 [REQUESTOR]
    -> Junction
Note: Send one feature per survey forward, to the featuremerger where we will attach the queries we're about to build
Junction
    -> Junction_2
Note: One feature per survey
Junction_2
    -> FeatureMerger_3 [REQUESTOR]
AttributeKeeper_2
    KEEP_ATTRS = Label,Name,RecordName,surveyid,_any_treat,_public_treat
    -> AttributeCreator
Note: Every column flagged to use will go into a query in the form H32A::Integer=1. Format this.
AttributeCreator
    ATTR_TABLE:
      SET_TO _qualColumn = tblfever.@LowerCase(@Value(Name))::Integer=1
      SET_TO _feverTableJoinCol = FME_CONDITIONAL:DEFAULT_VALUE'XXXX'BOOL_OP;OR;COMPOSITE_TEST;<Unused>;TEST @Value(RecordName) = REC43'HIDX'BOOL_OP;OR;COMPOSITE_TEST;<Unused>;TEST @Value(RecordName) = REC4A'HIDXA'FME_NUM_CONDITIONS3___
    -> Tester_2
    -> Tester
Tester
    BOOL_OP = AND
    TEST_DESCRIPTION = ""
    TEST_CLAUSE:
      TEST @Value(_any_treat) = y
      TEST @UpperCase(@Value(Name)) != H32Z
    TEST_MODE = Automatic
    PASSED -> FeatureMerger [SUPPLIER]
Note: The any-treat selector
Junction_4
    -> FeatureMerger_3 [SUPPLIER]
Tester_2
    BOOL_OP = AND
    TEST_DESCRIPTION = ""
    TEST_CLAUSE:
      TEST @Value(_public_treat) = y
      TEST @UpperCase(@Value(Name)) != H32Z
    TEST_MODE = Automatic
    PASSED -> Tester_5
Tester_5
    BOOL_OP = OR
    TEST_DESCRIPTION = ""
    TEST_CLAUSE = TEST @Value(_feverTableJoinCol) != XXXX
    TEST_MODE = Automatic
    PASSED -> FeatureMerger_2 [SUPPLIER]
    FAILED -> Non_Standard_Table_Rerun
Note: The public-treat selector
Junction_6
    -> FeatureMerger_3 [SUPPLIER]
Non_Standard_Table_Rerun: Inspector

Bookmark: Build the H32*=1 condition lists for each treatment category
FeatureMerger
    SUPPLIERS_FIRST = No
    MERGE_TYPE = Attributes Only
    ATTR_CONFLICT_RES = Use Requestor
    JOIN_KEYS = @Value(surveyid) @Value(surveyid) AUTO
    PROCESS_DUPS = No
    LIST_NAME = any_treat
    REJECT_NULL_MISSING_KEYS = No
    LIST_ATTRS_TO_INCLUDE = _qualColumn RecordName
    IGNORE_NULLS = No
    ATTR_ACCUM_MODE = Merge Supplier
    MERGED -> AttributeRemover
AttributeRemover
    REMOVE_ATTRS = Label,_qualColumn,Name,_any_treat,_public_treat
    -> ListConcatenator
ListConcatenator
    VAL_ATTR = _anyClause
    DROP_EMPTY_PARTS = No
    SEP = " OR "
    LIST_ATTR = any_treat{}._qualColumn
    -> Junction_3
    -> ListElementCounter
    -> ListDuplicateRemover
Note: Send the list of any-treatment clauses forward to merge onto the survey feature
Junction_3
    -> Junction_4
ListDuplicateRemover
    SRC_LIST = any_treat{}.RecordName
    -> ListElementCounter_3
ListElementCounter_3
    LIST_NAME = any_treat{}
    CNT_ATTR = _element_count
    -> Tester_6
Tester_6
    BOOL_OP = OR
    TEST_DESCRIPTION = ""
    TEST_CLAUSE = TEST @Value(_element_count) > 1
    TEST_MODE = Automatic
    PASSED -> MoreThanOneFeverTable
Note: Check that for each survey we are only joining one fever table (REC43 or REC4A but not both) and that we don't have >26 values defined (H32A-Z
MoreThanOneFeverTable: Inspector
ListElementCounter
    LIST_NAME = any_treat{}
    CNT_ATTR = _element_count
    -> Tester_3
Tester_3
    BOOL_OP = OR
    TEST_DESCRIPTION = ""
    TEST_CLAUSE = TEST @Value(_element_count) <= 26
    TEST_MODE = Automatic
    FAILED -> Too_Many_Any_Clauses
Too_Many_Any_Clauses: Inspector
FeatureMerger_2
    SUPPLIERS_FIRST = No
    MERGE_TYPE = Attributes Only
    ATTR_CONFLICT_RES = Use Requestor
    JOIN_KEYS = @Value(surveyid) @Value(surveyid) AUTO
    PROCESS_DUPS = No
    LIST_NAME = public_treat
    REJECT_NULL_MISSING_KEYS = No
    LIST_ATTRS_TO_INCLUDE = _qualColumn RecordName
    IGNORE_NULLS = No
    ATTR_ACCUM_MODE = Merge Supplier
    MERGED -> AttributeRemover_2
AttributeRemover_2
    REMOVE_ATTRS = Label,_qualColumn,Name,_any_treat,_public_treat
    -> ListConcatenator_2
ListConcatenator_2
    VAL_ATTR = _publicClause
    DROP_EMPTY_PARTS = No
    SEP = " OR "
    LIST_ATTR = public_treat{}._qualColumn
    -> Junction_5
    -> ListElementCounter_2
    -> ListDuplicateRemover_2
Note: Send the list of public-treatment clauses forward to merge onto the survey feature
Junction_5
    -> Junction_6
ListDuplicateRemover_2
    SRC_LIST = public_treat{}.RecordName
    -> ListElementCounter_4
ListElementCounter_4
    LIST_NAME = public_treat{}
    CNT_ATTR = _element_count
    -> Tester_7
Tester_7
    BOOL_OP = OR
    TEST_DESCRIPTION = ""
    TEST_CLAUSE = TEST @Value(_element_count) > 1
    TEST_MODE = Automatic
    PASSED -> MoreThanOneFeverTable_2
MoreThanOneFeverTable_2: Inspector
ListElementCounter_2
    LIST_NAME = public_treat{}
    CNT_ATTR = _element_count
    -> Tester_4
Tester_4
    BOOL_OP = OR
    TEST_DESCRIPTION = ""
    TEST_CLAUSE = TEST @Value(_element_count) <= 26
    TEST_MODE = Automatic
    FAILED -> Too_Many_Public_Clauses
Too_Many_Public_Clauses: Inspector

Bookmark: Build and run the queries
FeatureMerger_3
    SUPPLIERS_FIRST = No
    GEOM_TYPE = Build Polygons
    MERGE_TYPE = Attributes Only
    ATTR_CONFLICT_RES = Use Requestor
    JOIN_KEYS = @Value(surveyid) @Value(surveyid) AUTO
    PROCESS_DUPS = Yes
    REJECT_NULL_MISSING_KEYS = No
    CONNECT_Z_MODE = First Wins
    IGNORE_NULLS = No
    ATTR_ACCUM_MODE = Merge Supplier
    MERGED -> AttributeCreator_2
Note: No proportion for child, obvs
AttributeManager_CHILD
    ATTR_TABLE:
      REMOVE _childQuery
      REMOVE _wmnQuery
      REMOVE _clustQuery
      REMOVE _regionQuery
      REMOVE _nationalQuery
      REMOVE any_treat
      REMOVE had_fever
      REMOVE public_treat
    -> FeatureMerger_8 [REQUESTOR]

Bookmark: Build the queries for each survey
Note: Build the subquery for selecting the actual fever results
AttributeCreator_2
    ATTR_TABLE:
      SET_TO _feverQuery = (SELECT
        surveyid
        , caseid
        -- either HIDX or HIDXA depending on whether we are reading REC43 or REC4A
        , @Value(_feverTableJoinCol)
        , CASE WHEN tblfever.h22::Integer = 1 THEN 1 ELSE 0 END as had_fever
        , CASE WHEN tblfever.h22::Integer = 1 AND (
         @Value(_anyClause)
        ) THEN 1 ELSE 0 END AS any_treat
        , CASE WHEN tblfever.h22::Integer = 1 AND (
         @Value(_publicClause)
         ) THEN 1 ELSE 0 END AS public_treat
        FROM dhs_data_tables."@Value(RecordName)" tblfever
        ) fever
    -> AttributeCreator_3
Note: Build the overall queries for selecting each level of results
AttributeCreator_3
    ATTR_TABLE:
      SET_TO _childQuery = SELECT
        r21.bidx as child_num
        , r01.caseid as woman_id
        , r01.v001 as clusterid
        , r01.v024 as region
        , r01.v005 as wt
        , clust.latnum as latitude
        , clust.longnum as longitude
        , h0.hv025 as urban_rural
        , r11.v190 as wealth_quint
        , 1 as young_child
        , r01.v005::Float / 1000000 as young_child_wt
        , (had_fever) had_fever
        , (case when had_fever=1 THEN r01.v005::Float / 1000000 ELSE 0 END) as had_fever_wt
        , (any_treat) any_treat
        , (case when any_treat=1 THEN r01.v005::Float / 1000000 ELSE 0 END) as any_treat_wt
        , (public_treat) public_treat
        , (case when public_treat=1 THEN r01.v005::Float / 1000000 ELSE 0 END) as public_treat_wt
        FROM
        dhs_data_tables."REC21" r21
        INNER JOIN
        @Value(_feverQuery)
        ON
        r21.surveyid = fever.surveyid AND r21.caseid = fever.caseid AND r21.BIDX = fever.@Value(_feverTableJoinCol)
        INNER JOIN
        dhs_data_tables."REC01" r01
        ON r21.surveyid = r01.surveyid AND r21.caseid = r01.caseid
        LEFT OUTER JOIN
         dhs_data_tables."REC11" r11
        ON r01.surveyid::INTEGER = r11.surveyid::Integer AND r01.caseid = r11.caseid
        LEFT OUTER JOIN
        dhs_data_tables."RECH0" h0
        	-- dirty, but this is how it works
        	ON r01.surveyid = h0.surveyid AND LEFT(r01.caseid, -3) = h0.hhid
        LEFT OUTER JOIN
        dhs_data_locations.dhs_cluster_locs clust
        ON r01.surveyid::Integer = clust.surveyid AND r01.v001::Integer = clust.dhsclust
        WHERE r21.surveyid::Integer=@Value(surveyid) AND r21.b5 ::Integer=1 AND r21.b8::Integer<=5
        ORDER BY r21.surveyid::Integer, r01.v024::Integer, r01.v001::Integer, r01.caseid, r21.bidx::Integer
      SET_TO _wmnQuery = SELECT
        r01.caseid as woman_id
        , r01.v001 as clusterid
        , r01.v024 as region
        , clust.latnum as latitude
        , clust.longnum as longitude
        , h0.hv025 as urban_rural
        , r11.v190 as wealth_quint
        , sum(1) as young_child
        , sum(r01.v005::Float / 1000000) as young_child_wt
        , sum(had_fever) had_fever
        , sum(case when had_fever=1 THEN r01.v005::Float / 1000000 ELSE 0 END) as had_fever_wt
        , sum(any_treat) any_treat
        , sum(case when any_treat=1 THEN r01.v005::Float / 1000000 ELSE 0 END) as any_treat_wt
        , sum(public_treat) public_treat
        , sum(case when public_treat=1 THEN r01.v005::Float / 1000000 ELSE 0 END) as public_treat_wt
        FROM
        dhs_data_tables."REC21" r21
        INNER JOIN
        @Value(_feverQuery)
        ON
        r21.surveyid = fever.surveyid AND r21.caseid = fever.caseid AND r21.BIDX = fever.@Value(_feverTableJoinCol)
        INNER JOIN
        dhs_data_tables."REC01" r01
        ON r21.surveyid = r01.surveyid AND r21.caseid = r01.caseid
        LEFT OUTER JOIN
        dhs_data_tables."REC11" r11
        ON r01.surveyid::Integer = r11.surveyid::Integer AND r01.caseid = r11.caseid
        LEFT OUTER JOIN
        dhs_data_tables."RECH0" h0
        	-- dirty, but this is how it works
        	ON r01.surveyid = h0.surveyid AND LEFT(r01.caseid, -3) = h0.hhid
        LEFT OUTER JOIN
        dhs_data_locations.dhs_cluster_locs clust
        ON r01.surveyid::Integer = clust.surveyid AND r01.v001::Integer = clust.dhsclust
        WHERE r21.surveyid::Integer=@Value(surveyid) AND r21.b5 ::Integer=1 AND r21.b8::Integer<=5
        GROUP BY r01.surveyid, r01.caseid, r01.v001, r01.v024, clust.latnum, clust.longnum, h0.hv025, r11.v190
        ORDER BY r01.surveyid::Integer, r01.v024::Integer, r01.v001::Integer, r01.caseid
      SET_TO _clustQuery = SELECT
        r01.v001 as clusterid
        , r01.v024 as region
        , clust.latnum as latitude
        , clust.longnum as longitude
        , h0.hv025 as urban_rural
        , sum(1) as young_child
        , sum(r01.v005::Float / 1000000) as young_child_wt
        , sum(had_fever) had_fever
        , sum(case when had_fever=1 THEN r01.v005::Float / 1000000 ELSE 0 END) as had_fever_wt
        , sum(any_treat) any_treat
        , sum(case when any_treat=1 THEN r01.v005::Float / 1000000 ELSE 0 END) as any_treat_wt
        , sum(public_treat) public_treat
        , sum(case when public_treat=1 THEN r01.v005::Float / 1000000 ELSE 0 END) as public_treat_wt
        FROM
        dhs_data_tables."REC21" r21
        INNER JOIN
        @Value(_feverQuery)
        ON
        r21.surveyid = fever.surveyid AND r21.caseid = fever.caseid AND r21.BIDX = fever.@Value(_feverTableJoinCol)
        INNER JOIN
        dhs_data_tables."REC01" r01
        ON r21.surveyid = r01.surveyid AND r21.caseid = r01.caseid
        LEFT OUTER JOIN
        dhs_data_tables."RECH0" h0
        	-- dirty, but this is how it works
        	ON r01.surveyid = h0.surveyid AND LEFT(r01.caseid, -3) = h0.hhid
        LEFT OUTER JOIN
        dhs_data_locations.dhs_cluster_locs clust
        ON r01.surveyid::Integer = clust.surveyid AND r01.v001::Integer = clust.dhsclust
        WHERE r21.surveyid::Integer=@Value(surveyid) AND r21.b5 ::Integer=1 AND r21.b8::Integer<=5
        GROUP BY r01.surveyid, r01.v001, r01.v024, clust.latnum, clust.longnum, h0.hv025
        ORDER BY r01.surveyid::Integer, r01.v024::Integer, r01.v001::Integer
      SET_TO _regionQuery = SELECT
        r01.v024 as region
        , sum(1) as young_child
        , sum(r01.v005::Float / 1000000) as young_child_wt
        , sum(had_fever) had_fever
        , sum(case when had_fever=1 THEN r01.v005::Float / 1000000 ELSE 0 END) as had_fever_wt
        , sum(any_treat) any_treat
        , sum(case when any_treat=1 THEN r01.v005::Float / 1000000 ELSE 0 END) as any_treat_wt
        , sum(public_treat) public_treat
        , sum(case when public_treat=1 THEN r01.v005::Float / 1000000 ELSE 0 END) as public_treat_wt
        FROM
        dhs_data_tables."REC21" r21
        INNER JOIN
        @Value(_feverQuery)
        ON
        r21.surveyid = fever.surveyid AND r21.caseid = fever.caseid AND r21.BIDX = fever.@Value(_feverTableJoinCol)
        INNER JOIN
        dhs_data_tables."REC01" r01
        ON r21.surveyid = r01.surveyid AND r21.caseid = r01.caseid
        LEFT OUTER JOIN
        dhs_data_locations.dhs_cluster_locs clust
        ON r01.surveyid::Integer = clust.surveyid AND r01.v001::Integer = clust.dhsclust
        WHERE r21.surveyid::Integer=@Value(surveyid) AND r21.b5 ::Integer=1 AND r21.b8::Integer<=5
        GROUP BY r01.surveyid, r01.v024
        ORDER BY r01.surveyid::Integer, r01.v024::Integer
      SET_TO _nationalQuery = SELECT
        sum(1) as young_child
        , sum(r01.v005::Float / 1000000) as young_child_wt
        , sum(had_fever) had_fever
        , sum(case when had_fever=1 THEN r01.v005::Float / 1000000 ELSE 0 END) as had_fever_wt
        , sum(any_treat) any_treat
        , sum(case when any_treat=1 THEN r01.v005::Float / 1000000 ELSE 0 END) as any_treat_wt
        , sum(public_treat) public_treat
        , sum(case when public_treat=1 THEN r01.v005::Float / 1000000 ELSE 0 END) as public_treat_wt
        FROM
        dhs_data_tables."REC21" r21
        INNER JOIN
        @Value(_feverQuery)
        ON
        r21.surveyid = fever.surveyid AND r21.caseid = fever.caseid AND r21.BIDX = fever.@Value(_feverTableJoinCol)
        INNER JOIN
        dhs_data_tables."REC01" r01
        ON r21.surveyid = r01.surveyid AND r21.caseid = r01.caseid
        LEFT OUTER JOIN
        dhs_data_locations.dhs_cluster_locs clust
        ON r01.surveyid::Integer = clust.surveyid AND r01.v001::Integer = clust.dhsclust
        WHERE r21.surveyid::Integer=@Value(surveyid) AND r21.b5 ::Integer=1 AND r21.b8::Integer<=5
        GROUP BY r01.surveyid
        ORDER BY r01.surveyid::Integer
    -> AttributeKeeper_3
AttributeKeeper_3
    KEEP_ATTRS = _clustQuery,_childQuery,_nationalQuery,_regionQuery,surveyid,_wmnQuery
    -> SQLExecutor_WMN [INITIATOR]
    -> QueryInitiators
    -> SQLExecutor_CLST [INITIATOR]
    -> SQLExecutor_RGN [INITIATOR]
    -> SQLExecutor_NTL [INITIATOR]
    -> SQLExecutor_CHILD [INITIATOR]
    -> AttributeManager_10
    -> AttributeManager_12
    -> AttributeManager_13
    -> AttributeManager_14
    -> AttributeManager_15
QueryInitiators: Inspector

Bookmark: Run queries
SQLExecutor_WMN
    POSTGRES_NAMED_CONNECTION = DHS Data Readonly
    POSTGRES_QUERY_FEATURE_TYPES_FOR_MERGE_FILTERS = Yes
    FORMAT = POSTGRES
    COMBINE_ATTRS = Keep Result Attributes if Conflict
    DATASET = DHS Data Readonly
    SQL_STATEMENT = @Value(_wmnQuery)
    COMBINE_GEOM = Initiator Geometry Only
    EXPOSED_ATTRIBUTE_LIST = any_treat,any_treat_wt,clusterid,urban_rural,wealth_quint,had_fever,had_fever_wt,latitude,longitude,public_treat,public_treat_wt,region,survey_id,woman_id,young_child,young_child_wt
    RESULT -> AttributeManager
    <REJECTED> -> LOG_Rejected_SQL
SQLExecutor_RGN
    POSTGRES_NAMED_CONNECTION = DHS Data Readonly
    POSTGRES_QUERY_FEATURE_TYPES_FOR_MERGE_FILTERS = Yes
    FORMAT = POSTGRES
    COMBINE_ATTRS = Keep Result Attributes if Conflict
    DATASET = DHS Data Readonly
    SQL_STATEMENT = @Value(_regionQuery)
    COMBINE_GEOM = Initiator Geometry Only
    EXPOSED_ATTRIBUTE_LIST = any_treat,any_treat_wt,had_fever,had_fever_wt,public_treat,public_treat_wt,region,survey_id,young_child,young_child_wt
    RESULT -> AttributeManager_3
    <REJECTED> -> LOG_Rejected_SQL
SQLExecutor_CLST
    POSTGRES_NAMED_CONNECTION = DHS Data Readonly
    POSTGRES_QUERY_FEATURE_TYPES_FOR_MERGE_FILTERS = Yes
    FORMAT = POSTGRES
    COMBINE_ATTRS = Keep Result Attributes if Conflict
    DATASET = DHS Data Readonly
    SQL_STATEMENT = @Value(_clustQuery)
    COMBINE_GEOM = Initiator Geometry Only
    EXPOSED_ATTRIBUTE_LIST = any_treat,any_treat_wt,clusterid,urban_rural,had_fever,had_fever_wt,latitude,longitude,public_treat,public_treat_wt,region,survey_id,young_child,young_child_wt
    RESULT -> AttributeManager_2
    <REJECTED> -> LOG_Rejected_SQL
SQLExecutor_NTL
    POSTGRES_NAMED_CONNECTION = DHS Data Readonly
    POSTGRES_QUERY_FEATURE_TYPES_FOR_MERGE_FILTERS = Yes
    FORMAT = POSTGRES
    COMBINE_ATTRS = Keep Result Attributes if Conflict
    DATASET = DHS Data Readonly
    SQL_STATEMENT = @Value(_nationalQuery)
    COMBINE_GEOM = Initiator Geometry Only
    EXPOSED_ATTRIBUTE_LIST = any_treat,any_treat_wt,had_fever,had_fever_wt,public_treat,public_treat_wt,survey_id,young_child,young_child_wt
    RESULT -> AttributeManager_4
    <REJECTED> -> LOG_Rejected_SQL
SQLExecutor_CHILD
    POSTGRES_NAMED_CONNECTION = DHS Data Readonly
    POSTGRES_QUERY_FEATURE_TYPES_FOR_MERGE_FILTERS = Yes
    FORMAT = POSTGRES
    COMBINE_ATTRS = Keep Result Attributes if Conflict
    DATASET = DHS Data Readonly
    SQL_STATEMENT = @Value(_childQuery)
    COMBINE_GEOM = Initiator Geometry Only
    EXPOSED_ATTRIBUTE_LIST = any_treat,any_treat_wt,child_num,clusterid,urban_rural,wealth_quint,had_fever,had_fever_wt,latitude,longitude,public_treat,public_treat_wt,region,survey_id,woman_id,young_child,young_child_wt
    RESULT -> AttributeManager_CHILD
    RESULT -> StatisticsCalculator_WMN [off]
    RESULT -> StatisticsCalculator_CLUST [off]
    RESULT -> StatisticsCalculator_RGN [off]
    RESULT -> StatisticsCalculator_NTL [off]
    RESULT -> AttributeManager_CHILD_2
    <REJECTED> -> LOG_Rejected_SQL
LOG_Rejected_SQL: Logger
    MAXFEATS = 2000
    MAXCOORDS = 20
    MESSAGE = Rejected SQL feature:

Bookmark: Calculate proportions
AttributeManager
    ATTR_TABLE:
      REMOVE _childQuery
      REMOVE _wmnQuery
      REMOVE _clustQuery
      REMOVE _regionQuery
      REMOVE _nationalQuery
      RENAME_SET_VALUE young_child_wt > young_child_wt.wmncount
      RENAME_SET_VALUE had_fever_wt > had_fever_wt.wmncount
      RENAME_SET_VALUE public_treat_wt > public_treat_wt.wmncount
      RENAME_SET_VALUE any_treat_wt > any_treat_wt.wmncount
      SET_TO had_fever_wt.wmnprop = FME_CONDITIONAL:DEFAULT_VALUE'@Evaluate(@Value(had_fever_wt.wmncount)/@Value(young_child_wt.wmncount))'BOOL_OP;OR;COMPOSITE_TEST;<Unused>;TEST @Value(had_fever_wt.wmncount) = 0;TEST @Value(young_child_wt.wmncount) = 0'0'FME_NUM_CONDITIONS2___
      SET_TO fever_any_treat_wt.wmnprop = FME_CONDITIONAL:DEFAULT_VALUE'@Evaluate(@Value(any_treat_wt.wmncount)/@Value(had_fever_wt.wmncount))'BOOL_OP;OR;COMPOSITE_TEST;<Unused>;TEST @Value(had_fever_wt.wmncount) = 0;TEST @Value(any_treat_wt.wmncount) = 0'0'FME_NUM_CONDITIONS2___
      SET_TO fever_public_treat_wt.wmnprop = FME_CONDITIONAL:DEFAULT_VALUE'@Evaluate(@Value(public_treat_wt.wmncount)/@Value(had_fever_wt.wmncount))'BOOL_OP;OR;COMPOSITE_TEST;<Unused>;TEST @Value(had_fever_wt.wmncount) = 0;TEST @Value(public_treat_wt.wmncount) = 0'0'FME_NUM_CONDITIONS2___
    -> FeatureMerger_4 [REQUESTOR]
AttributeManager_3
    ATTR_TABLE:
      REMOVE _childQuery
      REMOVE _wmnQuery
      REMOVE _clustQuery
      REMOVE _regionQuery
      REMOVE _nationalQuery
      RENAME_SET_VALUE any_treat_wt > any_treat_wt.regioncount
      RENAME_SET_VALUE had_fever_wt > had_fever_wt.regioncount
      RENAME_SET_VALUE public_treat_wt > public_treat_wt.regioncount
      RENAME_SET_VALUE young_child_wt > young_child_wt.regioncount
      SET_TO had_fever_wt.regionprop = @Evaluate(@Value(had_fever_wt.regioncount)/@Value(young_child_wt.regioncount))
      SET_TO fever_any_treat_wt.regionprop = @Evaluate(@Value(any_treat_wt.regioncount)/@Value(had_fever_wt.regioncount))
      SET_TO fever_public_treat_wt.regionprop = @Evaluate(@Value(public_treat_wt.regioncount)/@Value(had_fever_wt.regioncount))
    -> FeatureMerger_6 [REQUESTOR]
AttributeManager_2
    ATTR_TABLE:
      REMOVE _childQuery
      REMOVE _wmnQuery
      REMOVE _clustQuery
      REMOVE _regionQuery
      REMOVE _nationalQuery
      RENAME_SET_VALUE any_treat_wt > any_treat_wt.clustcount
      RENAME_SET_VALUE had_fever_wt > had_fever_wt.clustcount
      RENAME_SET_VALUE public_treat_wt > public_treat_wt.clustcount
      RENAME_SET_VALUE young_child_wt > young_child_wt.clustcount
      SET_TO had_fever_wt.clustprop = FME_CONDITIONAL:DEFAULT_VALUE'@Evaluate(@Value(had_fever_wt.clustcount)/@Value(young_child_wt.clustcount))'BOOL_OP;OR;COMPOSITE_TEST;<Unused>;TEST @Value(young_child_wt.clustcount) = 0;TEST @Value(had_fever_wt.clustcount) = 0'0'FME_NUM_CONDITIONS2___
      SET_TO fever_any_treat_wt.clustprop = FME_CONDITIONAL:DEFAULT_VALUE'@Evaluate(@Value(any_treat_wt.clustcount)/@Value(had_fever_wt.clustcount))'BOOL_OP;OR;COMPOSITE_TEST;<Unused>;TEST @Value(any_treat_wt.clustcount) = 0;TEST @Value(had_fever_wt.clustcount) = 0'0'FME_NUM_CONDITIONS2___
      SET_TO fever_public_treat_wt.clustprop = FME_CONDITIONAL:DEFAULT_VALUE'@Evaluate(@Value(public_treat_wt.clustcount)/@Value(had_fever_wt.clustcount))'BOOL_OP;OR;COMPOSITE_TEST;<Unused>;TEST @Value(had_fever_wt.clustcount) = 0;TEST @Value(public_treat_wt.clustcount) = 0'0'FME_NUM_CONDITIONS2___
    -> FeatureMerger_5 [REQUESTOR]
    -> StatisticsCalculator
    -> AttributeManager_19
AttributeManager_4
    ATTR_TABLE:
      REMOVE _childQuery
      REMOVE _wmnQuery
      REMOVE _clustQuery
      REMOVE _regionQuery
      REMOVE _nationalQuery
      RENAME_SET_VALUE any_treat_wt > any_treat_wt.nationalcount
      RENAME_SET_VALUE had_fever_wt > had_fever_wt.nationalcount
      RENAME_SET_VALUE public_treat_wt > public_treat_wt.nationalcount
      RENAME_SET_VALUE young_child_wt > young_child_wt.nationalcount
      SET_TO had_fever_wt.nationalprop = @Evaluate(@Value(had_fever_wt.nationalcount)/@Value(young_child_wt.nationalcount))
      SET_TO fever_any_treat_wt.nationalprop = @Evaluate(@Value(any_treat_wt.nationalcount)/@Value(had_fever_wt.nationalcount))
      SET_TO fever_public_treat_wt.nationalprop = @Evaluate(@Value(public_treat_wt.nationalcount)/@Value(had_fever_wt.nationalcount))
    -> FeatureMerger_9 [REQUESTOR]

Bookmark: Estimate CIs: ORIGINAL from cluster mean+-stderr
Note: Basic estimation of 95% CIs with central limit theorem, assuming normal distribution. Which seems iffy to me as the data are unlikely to be near-normal.
StatisticsCalculator
    STATS_ATTRS = fever_any_treat_wt.clustprop fever_public_treat_wt.clustprop
    PREPEND_ATTR_NAME_CHOICE = For multiple results only
    NUMERIC_ATTR = _numeric_count
    COMPUTE_HISTOGRAM = NO
    STDEV_ATTR = _stdev
    GROUP_BY = surveyid
    MEAN_ATTR = _mean
    SUMMARY -> AttributeManager_17
AttributeManager_17
    ATTR_TABLE:
      RENAME_SET_VALUE fever_any_treat_wt.clustprop._numeric_count > fever_any_treat_wt_numeric_count
      RENAME_SET_VALUE fever_any_treat_wt.clustprop._mean > fever_any_treat_wt_mean
      RENAME_SET_VALUE fever_any_treat_wt.clustprop._stdev > fever_any_treat_wt_stdev
      SET_TO fever_any_treat_wt_stderr = @Evaluate(@Value(fever_any_treat_wt_stdev)/@sqrt(@Value(fever_any_treat_wt_numeric_count)))
      RENAME_SET_VALUE fever_public_treat_wt.clustprop._numeric_count > fever_public_treat_wt_numeric_count
      RENAME_SET_VALUE fever_public_treat_wt.clustprop._mean > fever_public_treat_wt_mean
      RENAME_SET_VALUE fever_public_treat_wt.clustprop._stdev > fever_public_treat_wt_stdev
      SET_TO fever_public_treat_wt_stderr = @Evaluate(@Value(fever_public_treat_wt_stdev)/@sqrt(@Value(fever_public_treat_wt_numeric_count)))
    -> FeatureMerger_9 [SUPPLIER]

Bookmark: Estimate CIs: FIX1: bootstrap cluster props
Note: Bootstrap the confidence intervals using a non-parametric method. Implemented in R using the bootBCa package: http://bootbca.r-forge.r-project.org/ / Requires R to be configured in FME and the following packages installed AT THE SYSTEM LEVEL: / bootBCa, plyr, foreach, doParallel. Disable these transformers if they're not!
AttributeManager_19
    ATTR_TABLE:
      REMOVE clusterid
      REMOVE latitude
      REMOVE longitude
      REMOVE region
      REMOVE any_treat_wt.clustcount
      REMOVE public_treat_wt.clustcount
      REMOVE young_child_wt.clustcount
      REMOVE any_treat
      REMOVE had_fever
      REMOVE public_treat
      REMOVE survey_id
      REMOVE young_child
      REMOVE urban_rural
    -> RCaller [clusterdata]
RCaller
    QUERY_DEF:
      Output,library(bootBCa)
      library(plyr)
      # these next two libraries are required for running copies of the function (one per survey) in parallel
      # on windows - there are other choices than doParallel esp on linux
      library(foreach)
      library(doParallel)

      # function to create bootstrapped 95% confidence intervals on the fever_public_treat_wt.clustprop
      # and fever_any_treat_wt.clustprop columns of the provided dataframe. also adds normal standard errors
      # just for comparison to FME-calculated values for checking
      createCIs <- function(dfInput){
        # import the required library within the function as this code gets passed to independent
        # processes by the paralleliser, sans environment
        library(bootBCa)
        # correct the cluster proportions according to the size of the cluster (such that the mean of the values is the same as the
        # mean of the original child-level data, and thus the same as the national mean to which we will apply the CIs we create here)
        avgClust <- mean(dfInput$had_fever_wt.clustcount)
        clustWts <- dfInput$had_fever_wt.clustcount / avgClust
        corrPubProp <- dfInput$fever_public_treat_wt.clustprop * clustWts
        corrAnyProp <- dfInput$fever_any_treat_wt.clustprop * clustWts
        # calculate the bootstrapped 95% CIs
        valsPub <- na.omit(corrPubProp)
        valsAny<-na.omit(corrAnyProp)
        # don't attempt to call BCa if no data as it will crash the processing rather than return na
        if (length(valsPub > 0)){
          bsPub<-BCa(valsPub, 0.01, mean, alpha=c(0.025,0.975))
        } else {
          bsPub <- c("0.025"=0, "0.975"=0)
        }
        if (length(valsAny > 0)){
          bsAny<-BCa(valsAny, 0.01, mean, alpha=c(0.025,0.975))
        } else {
          bsAny <- c("0.025"=0, "0.975"=0)
        }
        # also add the se just so we can check them against the FME calculated values to make sure all is working
        sePublic <- sd(valsPub)/sqrt(length(valsPub))
        seAny <- sd(valsAny)/sqrt(length(valsAny))
        # need to use the weighted mean for the CI calcualtion. FME will have this from the national data anyway but
        # we expose it here to make sure we're getting things right...
        meanPublic <- mean(valsPub)
        meanAny <- mean(valsAny)
        # columns added to the dataframe here are what we need to expose in the Attributes To Expose field
        dfOut<-data.frame(bs_lci_pub=bsPub["0.025"], bs_uci_pub=bsPub["0.975"],
          bs_lci_any=bsAny["0.025"], bs_uci_any=bsAny["0.975"],
          se_public=sePublic, se_any=seAny,
          mean_public=meanPublic, mean_any=meanAny)
        return(dfOut)
      }

      # how many cores to use - my machine has 12, adjust to suit
      workers <- makeCluster(10)
      registerDoParallel(workers)

      # output a dataframe containing one row (=fme feature) for each input survey, by calling the
      # createCIs function for each survey's data in turn (like GROUP BY)
      # Use parallel functionality to ensure it runs in a decent amount of time. On a single core
      # with all 200+ surveys it takes 10 minutes+ and this times out in FME making the translation fail.
      fmeOutput <- ddply(clusterdata, "surveyid", createCIs, .parallel = TRUE)
      ,surveyid bs_lci_pub bs_uci_pub bs_lci_any bs_uci_any se_public se_any mean_public mean_any
    OUTPUT_SCHEMA = surveyid bs_lci_pub bs_uci_pub bs_lci_any bs_uci_any se_public se_any mean_public mean_any
    TABLE_DEF = clusterdata,surveyid,text,had_fever_wt.clustcount,"real(20,10)",had_fever_wt.clustprop,"real(20,10)",fever_any_treat_wt.clustprop,"real(20,10)",fever_public_treat_wt.clustprop,"real(20,10)"
    -> FeatureMerger_9 [SUPPLIER]

Bookmark: Write out the SQL for reference
AttributeManager_10 [off]
    ATTR_TABLE:
      RENAME_SET_VALUE _childQuery > _sqlOutput
      REMOVE _wmnQuery
      REMOVE _clustQuery
      REMOVE _regionQuery
      REMOVE _nationalQuery
      SET_TO _sqlFN = @Value(surveyid).FST.ChildQuery.sql
    -> AttributeManager_16
AttributeManager_12 [off]
    ATTR_TABLE:
      REMOVE _childQuery
      RENAME_SET_VALUE _wmnQuery > _sqlOutput
      REMOVE _clustQuery
      REMOVE _regionQuery
      REMOVE _nationalQuery
      SET_TO _sqlFN = @Value(surveyid).FST.WomenQuery.sql
    -> AttributeManager_16
AttributeManager_13
    ATTR_TABLE:
      REMOVE _childQuery
      REMOVE _wmnQuery
      RENAME_SET_VALUE _clustQuery > _sqlOutput
      REMOVE _regionQuery
      REMOVE _nationalQuery
      SET_TO _sqlFN = @Value(surveyid).FST.ClustQuery.sql
    -> AttributeManager_16
AttributeManager_14 [off]
    ATTR_TABLE:
      REMOVE _childQuery
      REMOVE _wmnQuery
      REMOVE _clustQuery
      RENAME_SET_VALUE _regionQuery > _sqlOutput
      REMOVE _nationalQuery
      SET_TO _sqlFN = @Value(surveyid).FST.RegionQuery.sql
    -> AttributeManager_16
AttributeManager_15
    ATTR_TABLE:
      REMOVE _childQuery
      REMOVE _wmnQuery
      REMOVE _clustQuery
      REMOVE _regionQuery
      RENAME_SET_VALUE _nationalQuery > _sqlOutput
      SET_TO _sqlFN = @Value(surveyid).FST.NationalQuery.sql
    -> AttributeManager_16
Note: text file writer is surprisingly not your friend for this
AttributeManager_16
    ATTR_TABLE = SET_TO _sqlPath = $(DestDataset_CSV2)\generated_sql\@Value(_sqlFN)
    -> AttributeFileWriter
AttributeFileWriter
    SOURCE_ATTR = _sqlOutput
    CHAR_ENCODING = fme-system
    OVERWRITE_FILE = Overwrite file
    FILE_NAME = @Value(_sqlPath)

Bookmark: Summarise the results
Note: We could avoid hitting the database so much by just running the child-level query and then summarising the results here in FME using these statistics calculators. However I could only get 1 or 2 at once to respect the group ordering and spit out the features on the fly. The rest held on to them until the end, resulting in catastrophic slowness and memory usage. These statistic calculators are just left in for reference.
StatisticsCalculator_WMN [off]
    STATS_ATTRS = public_treat_wt any_treat_wt had_fever_wt young_child_wt
    SUM_ATTR = wmncount
    PREPEND_ATTR_NAME_CHOICE = For all results
    COMPUTE_HISTOGRAM = NO
    GROUP_BY = latitude region woman_id surveyid longitude clusterid
    SUMMARY -> woman [off]
woman: Inspector [off]
StatisticsCalculator_CLUST [off]
    STATS_ATTRS = public_treat_wt any_treat_wt had_fever_wt young_child_wt
    SUM_ATTR = clustcount
    PREPEND_ATTR_NAME_CHOICE = For all results
    COMPUTE_HISTOGRAM = NO
    GROUP_BY = latitude region surveyid longitude clusterid
    SUMMARY -> cluster [off]
cluster: Inspector [off]
StatisticsCalculator_RGN [off]
    STATS_ATTRS = public_treat_wt any_treat_wt had_fever_wt young_child_wt
    SUM_ATTR = regioncount
    PREPEND_ATTR_NAME_CHOICE = For all results
    COMPUTE_HISTOGRAM = NO
    GROUP_BY = region surveyid
    SUMMARY -> region [off]
region: Inspector [off]
StatisticsCalculator_NTL [off]
    STATS_ATTRS = public_treat_wt any_treat_wt had_fever_wt young_child_wt
    SUM_ATTR = nationalcount
    PREPEND_ATTR_NAME_CHOICE = For all results
    COMPUTE_HISTOGRAM = NO
    GROUP_BY = surveyid
    SUMMARY -> national [off]
national: Inspector [off]

Bookmark: Estimate CIs: FIX2 from child data
Note: This is the "correct" way of estimating CIs for the national estimates as it uses the data from which the national estimates are derived, i.e. the child data as opposed to cluster summaries
AttributeManager_CHILD_2
    ATTR_TABLE:
      REMOVE _childQuery
      REMOVE _wmnQuery
      REMOVE _clustQuery
      REMOVE _regionQuery
      REMOVE _nationalQuery
      REMOVE child_num
      REMOVE woman_id
      REMOVE clusterid
      REMOVE latitude
      REMOVE longitude
      REMOVE region
      REMOVE had_fever_wt
      REMOVE any_treat_wt
      REMOVE public_treat_wt
      REMOVE survey_id
      REMOVE young_child
      REMOVE urban_rural
      REMOVE wealth_quint
    -> Tester_9
Tester_9
    BOOL_OP = OR
    TEST_DESCRIPTION = ""
    TEST_CLAUSE = TEST @Value(had_fever) > 0
    TEST_MODE = Automatic
    PASSED -> RCaller_3 [childraw]
RCaller_3
    QUERY_DEF:
      Output,library(plyr)
      # these next two libraries are required for running copies of the function (one per survey) in parallel
      # on windows - there are other choices than doParallel esp on linux
      library(foreach)
      library(doParallel)

      # function to create 95% confidence intervals for the national proportions based on the raw
      # child level had-treatment data. Input data should contain only children who had fever.
      createCIs <- function(dfInput){
        library(survey)
        # create GLMs for the relationship between the response column and the predictor "1"
        pubmod <- glm(public_treat~1, data=dfInput, family=quasibinomial(), weights=young_child_wt)
        anymod <- glm(any_treat~1, data=dfInput, family=quasibinomial(), weights=young_child_wt)

        dfOut <- tryCatch({
            meanpub <- plogis(coef(pubmod))
            confpub <- plogis(confint(pubmod))
            meanany <- plogis(coef(anymod))
            confany <- plogis(confint(anymod))

            # create a survey design object to use the survey package for estimating CIs
            SVY <- svydesign(id=~1, weights=~young_child_wt, data=dfInput)
            coefpub <- svymean(~public_treat, SVY, deff=FALSE, na.rm=TRUE)
            coefany <- svymean(~any_treat, SVY, deff=FALSE, na.rm=TRUE)
            svyconfpub <- confint(coefpub)
            svyconfany <- confint(coefany)

            data.frame(glm_mean_public=meanpub, glm_lci_public=confpub["2.5 %"], glm_uci_public=confpub["97.5 %"],
              glm_mean_any=meanany, glm_lci_any=confany["2.5 %"], glm_uci_any=confany["97.5 %"],
              svy_lci_public=svyconfpub[1], svy_uci_public=svyconfpub[2],
              svy_lci_any=svyconfany[1], svy_uci_any=svyconfany[2])
        },
        error=function(cond){
            return (data.frame(glm_mean_public=-9999, glm_lci_public=-9999, glm_uci_public=-9999,
              glm_mean_any=-9999, glm_lci_any=-9999, glm_uci_any=-9999))
        },
        warning=function(cond){return(NULL)}
        )
        return (dfOut)
      }

      # how many cores to use - my machine has 12, adjust to suit
      workers <- makeCluster(10)
      registerDoParallel(workers)

      # output a dataframe containing one row (=fme feature) for each input survey, by calling the
      # createCIs function for each survey's data in turn (like GROUP BY)
      # Use parallel functionality to ensure it runs in a decent amount of time. On a single core
      # with all 200+ surveys it takes 10 minutes+ and this times out in FME making the translation fail.
      fmeOutput <- ddply(childraw, "surveyid", createCIs, .parallel = TRUE)
      ,surveyid glm_mean_public glm_lci_public glm_uci_public glm_mean_any glm_lci_any glm_uci_any svy_lci_public svy_uci_public svy_lci_any svy_uci_any
    OUTPUT_SCHEMA = surveyid glm_mean_public glm_lci_public glm_uci_public glm_mean_any glm_lci_any glm_uci_any svy_lci_public svy_uci_public svy_lci_any svy_uci_any
    TABLE_DEF = childraw,surveyid,text,any_treat,integer,had_fever,integer,young_child_wt,"real(20,10)",public_treat,integer
    -> FeatureMerger_9 [SUPPLIER]

Bookmark: Attach CIs to national figures
FeatureMerger_9
    SUPPLIERS_FIRST = No
    GEOM_TYPE = Build Polygons
    MERGE_TYPE = Attributes Only
    ATTR_CONFLICT_RES = Use Requestor
    JOIN_KEYS = @Value(surveyid) @Value(surveyid) AUTO
    PROCESS_DUPS = Yes
    REJECT_NULL_MISSING_KEYS = No
    CONNECT_Z_MODE = First Wins
    IGNORE_NULLS = No
    ATTR_ACCUM_MODE = Merge Supplier
    MERGED -> AttributeManager_18
AttributeManager_18
    ATTR_TABLE:
      SET_TO fever_public_treat_wt.nationalprop_LCI_CL = @Evaluate(@Value(fever_public_treat_wt.nationalprop)-1.96*@Value(fever_public_treat_wt_stderr))
      SET_TO fever_public_treat_wt.nationalprop_UCI_CL = @Evaluate(@Value(fever_public_treat_wt.nationalprop)+1.96*@Value(fever_public_treat_wt_stderr))
      SET_TO fever_any_treat_wt.nationalprop_LCI_CL = @Evaluate(@Value(fever_any_treat_wt.nationalprop)-1.96*@Value(fever_any_treat_wt_stderr))
      SET_TO fever_any_treat_wt.nationalprop_UCI_CL = @Evaluate(@Value(fever_any_treat_wt.nationalprop)+1.96*@Value(fever_any_treat_wt_stderr))
      RENAME_SET_VALUE se_public > se_public_r
      RENAME_SET_VALUE se_any > se_any_r
      RENAME_SET_VALUE mean_public > mean_public_r
      RENAME_SET_VALUE mean_any > mean_any_r
    -> FeatureMerger_7 [REQUESTOR]

Bookmark: Format and save the outputs
CSV (reader CSV2_1)
    attributes: SurveyId string, DHS_CountryCode string, SurveyYear string, SurveyType string, SurveyStatus string, CountryName string, SurveyYearLabel string, SurveyNum string, IndicatorData string, RegionName string, SubregionName string, PublicationDate string, ReleaseDate string, SurveyCharacteristicIds string, Footnotes string, FieldworkStart string, FieldworkEnd string, ImplementingOrg string, NumberOfSamplePoints string, NumberofHouseholds string, UniverseOfWomen string, NumberOfWomen string, MinAgeWomen string, MaxAgeWomen string, UniverseOfMen string, NumberOfMen string, MinAgeMen string, MaxAgeMen string, NumberOfFacilities string
    -> AttributeManager_5
Note: Read survey info from API and format to attach
AttributeManager_5
    ATTR_TABLE:
      RENAME_SET_VALUE SurveyId > SurveyName
      RENAME_SET_VALUE SurveyNum > SurveyId
    -> FeatureMerger_4 [SUPPLIER]
    -> FeatureMerger_5 [SUPPLIER]
    -> FeatureMerger_6 [SUPPLIER]
    -> FeatureMerger_7 [SUPPLIER]
    -> FeatureMerger_8 [SUPPLIER]
FeatureMerger_4
    SUPPLIERS_FIRST = Yes
    MERGE_TYPE = Attributes Only
    ATTR_CONFLICT_RES = Use Requestor
    JOIN_KEYS = @Value(surveyid) @Value(SurveyId) AUTO
    PROCESS_DUPS = No
    REJECT_NULL_MISSING_KEYS = No
    IGNORE_NULLS = No
    ATTR_ACCUM_MODE = Merge Supplier
    MERGED -> AttributeManager_6
    UNMERGED_REQUESTOR -> AttributeManager_6
AttributeManager_6
    ATTR_TABLE:
      REMOVE SurveyId
      RENAME_SET_VALUE surveyid > SurveyId
      SET_TO _OutFN = FST_ByWoman_@Value(SurveyId)_@Value(SurveyName)
      SET_TO _OutFN_Single = FST_ByWoman_ALL
    -> File1 (writer CSV2_3)
    -> File101 (writer CSV2_3)
File1 (writer CSV2_3)
    attributes: SurveyName string, SurveyId string, DHS_CountryCode string, SurveyYear string, SurveyType string, SurveyStatus string, CountryName string, SurveyYearLabel string, woman_id string, clusterid string, latitude string, longitude string, region string, urban_rural string, wealth_quint string, young_child_wt.wmncount string, had_fever_wt.wmncount string, public_treat_wt.wmncount string, any_treat_wt.wmncount string, had_fever_wt.wmnprop string, fever_public_treat_wt.wmnprop string, fever_any_treat_wt.wmnprop string
File101 (writer CSV2_3)
    attributes: SurveyName string, SurveyId string, DHS_CountryCode string, SurveyYear string, SurveyType string, SurveyStatus string, CountryName string, SurveyYearLabel string, woman_id string, clusterid string, latitude string, longitude string, region string, urban_rural string, wealth_quint string, young_child_wt.wmncount string, had_fever_wt.wmncount string, public_treat_wt.wmncount string, any_treat_wt.wmncount string, had_fever_wt.wmnprop string, fever_public_treat_wt.wmnprop string, fever_any_treat_wt.wmnprop string
FeatureMerger_6
    SUPPLIERS_FIRST = Yes
    MERGE_TYPE = Attributes Only
    ATTR_CONFLICT_RES = Use Requestor
    JOIN_KEYS = @Value(surveyid) @Value(SurveyId) AUTO
    PROCESS_DUPS = No
    REJECT_NULL_MISSING_KEYS = No
    IGNORE_NULLS = No
    ATTR_ACCUM_MODE = Merge Supplier
    MERGED -> AttributeManager_8
    UNMERGED_REQUESTOR -> AttributeManager_8
AttributeManager_8
    ATTR_TABLE:
      REMOVE SurveyId
      RENAME_SET_VALUE surveyid > SurveyId
      SET_TO _OutFN = FST_ByRegion_@Value(SurveyId)_@Value(SurveyName)
      SET_TO _OutFN_Single = FST_ByRegion_ALL
    -> File10000 (writer CSV2_3)
    -> File1000001 (writer CSV2_3)
File10000 (writer CSV2_3)
    attributes: SurveyName string, SurveyId string, DHS_CountryCode string, SurveyYear string, SurveyType string, SurveyStatus string, CountryName string, SurveyYearLabel string, region string, young_child_wt.regioncount string, had_fever_wt.regioncount string, public_treat_wt.regioncount string, any_treat_wt.regioncount string, had_fever_wt.regionprop string, fever_public_treat_wt.regionprop string, fever_any_treat_wt.regionprop string
File1000001 (writer CSV2_3)
    attributes: SurveyName string, SurveyId string, DHS_CountryCode string, SurveyYear string, SurveyType string, SurveyStatus string, CountryName string, SurveyYearLabel string, region string, young_child_wt.regioncount string, had_fever_wt.regioncount string, public_treat_wt.regioncount string, any_treat_wt.regioncount string, had_fever_wt.regionprop string, fever_public_treat_wt.regionprop string, fever_any_treat_wt.regionprop string
FeatureMerger_5
    SUPPLIERS_FIRST = Yes
    MERGE_TYPE = Attributes Only
    ATTR_CONFLICT_RES = Use Requestor
    JOIN_KEYS = @Value(surveyid) @Value(SurveyId) AUTO
    PROCESS_DUPS = No
    REJECT_NULL_MISSING_KEYS = No
    IGNORE_NULLS = No
    ATTR_ACCUM_MODE = Merge Supplier
    MERGED -> AttributeManager_7
    UNMERGED_REQUESTOR -> AttributeManager_7
AttributeManager_7
    ATTR_TABLE:
      REMOVE SurveyId
      RENAME_SET_VALUE surveyid > SurveyId
      SET_TO _OutFN = FST_ByCluster_@Value(SurveyId)_@Value(SurveyName)
      SET_TO _OutFN_Single = FST_ByCluster_ALL
    -> File100 (writer CSV2_3)
    -> File10001 (writer CSV2_3)
File100 (writer CSV2_3)
    attributes: SurveyName string, SurveyId string, DHS_CountryCode string, SurveyYear string, SurveyType string, SurveyStatus string, CountryName string, SurveyYearLabel string, clusterid string, latitude string, longitude string, region string, urban_rural string, young_child_wt.clustcount string, had_fever_wt.clustcount string, public_treat_wt.clustcount string, any_treat_wt.clustcount string, had_fever_wt.clustprop string, fever_public_treat_wt.clustprop string, fever_any_treat_wt.clustprop string
File10001 (writer CSV2_3)
    attributes: SurveyName string, SurveyId string, DHS_CountryCode string, SurveyYear string, SurveyType string, SurveyStatus string, CountryName string, SurveyYearLabel string, clusterid string, latitude string, longitude string, region string, urban_rural string, young_child_wt.clustcount string, had_fever_wt.clustcount string, public_treat_wt.clustcount string, any_treat_wt.clustcount string, had_fever_wt.clustprop string, fever_public_treat_wt.clustprop string, fever_any_treat_wt.clustprop string
FeatureMerger_8
    SUPPLIERS_FIRST = Yes
    MERGE_TYPE = Attributes Only
    ATTR_CONFLICT_RES = Use Requestor
    JOIN_KEYS = @Value(surveyid) @Value(SurveyId) AUTO
    PROCESS_DUPS = No
    REJECT_NULL_MISSING_KEYS = No
    IGNORE_NULLS = No
    ATTR_ACCUM_MODE = Merge Supplier
    MERGED -> AttributeManager_11
    UNMERGED_REQUESTOR -> AttributeManager_11
AttributeManager_11
    ATTR_TABLE:
      REMOVE SurveyId
      RENAME_SET_VALUE surveyid > SurveyId
      REMOVE survey_id
      REMOVE young_child
      SET_TO _OutFN = FST_ByChild_@Value(SurveyId)_@Value(SurveyName)
      SET_TO _OutFN_Single = FST_ByChild_ALL
    -> File100000000 (writer CSV2_3)
    -> File10000000000 (writer CSV2_3)
File100000000 (writer CSV2_3)
    attributes: SurveyName string, SurveyId string, DHS_CountryCode string, SurveyYear string, SurveyType string, SurveyStatus string, CountryName string, SurveyYearLabel string, child_num string, woman_id string, clusterid string, latitude string, longitude string, region string, urban_rural string, wealth_quint string, young_child_wt string, had_fever_wt string, public_treat_wt string, any_treat_wt string
File10000000000 (writer CSV2_3)
    attributes: SurveyName string, SurveyId string, DHS_CountryCode string, SurveyYear string, SurveyType string, SurveyStatus string, CountryName string, SurveyYearLabel string, child_num string, woman_id string, clusterid string, latitude string, longitude string, region string, urban_rural string, wealth_quint string, young_child_wt string, had_fever_wt string, public_treat_wt string, any_treat_wt string
FeatureMerger_7
    SUPPLIERS_FIRST = Yes
    MERGE_TYPE = Attributes Only
    ATTR_CONFLICT_RES = Use Requestor
    JOIN_KEYS = @Value(surveyid) @Value(SurveyId) AUTO
    PROCESS_DUPS = No
    REJECT_NULL_MISSING_KEYS = No
    IGNORE_NULLS = No
    ATTR_ACCUM_MODE = Merge Supplier
    MERGED -> AttributeManager_9
    UNMERGED_REQUESTOR -> Missing_National_Svy_Info
    UNMERGED_REQUESTOR -> AttributeManager_9
AttributeManager_9
    ATTR_TABLE:
      REMOVE SurveyId
      RENAME_SET_VALUE surveyid > SurveyId
      SET_TO _OutFN = FST_BySurvey_@Value(SurveyId)_@Value(SurveyName)
      SET_TO _OutFN_Single = FST_BySurvey_ALL
      RENAME_SET_VALUE fever_any_treat_wt_mean > fever_any_treat_wt_clustermean
      RENAME_SET_VALUE fever_any_treat_wt_stdev > fever_any_treat_wt_clusterstdev
      RENAME_SET_VALUE fever_any_treat_wt_stderr > fever_any_treat_wt_clusterstderr
      RENAME_SET_VALUE fever_public_treat_wt_mean > fever_public_treat_wt_clustermean
      RENAME_SET_VALUE fever_public_treat_wt_stdev > fever_public_treat_wt_clusterstdev
      RENAME_SET_VALUE fever_public_treat_wt_stderr > fever_public_treat_wt_clusterstderr
      RENAME_SET_VALUE bs_lci_pub > fever_public_treat_wt.nationalprop_LCI_BS
      RENAME_SET_VALUE bs_uci_pub > fever_public_treat_wt.nationalprop_UCI_BS
      RENAME_SET_VALUE bs_lci_any > fever_any_treat_wt.nationalprop_LCI_BS
      RENAME_SET_VALUE bs_uci_any > fever_any_treat_wt.nationalprop_UCI_BS
      RENAME_SET_VALUE glm_mean_public > mean_public_glm
      RENAME_SET_VALUE glm_lci_public > fever_public_treat_wt.nationalprop_LCI_GLM
      RENAME_SET_VALUE glm_uci_public > fever_public_treat_wt.nationalprop_UCI_GLM
      RENAME_SET_VALUE glm_mean_any > mean_any_glm
      RENAME_SET_VALUE glm_lci_any > fever_any_treat_wt.nationalprop_LCI_GLM
      RENAME_SET_VALUE glm_uci_any > fever_any_treat_wt.nationalprop_UCI_GLM
      RENAME_SET_VALUE svy_lci_public > fever_public_treat_wt.nationalprop_LCI_SVY
      RENAME_SET_VALUE svy_uci_public > fever_public_treat_wt.nationalprop_UCI_SVY
      RENAME_SET_VALUE svy_lci_any > fever_any_treat_wt.nationalprop_LCI_SVY
      RENAME_SET_VALUE svy_uci_any > fever_any_treat_wt.nationalprop_UCI_SVY
    -> bob (writer CSV2_3)
    -> File100000001 (writer CSV2_3)
    -> natl_output_check_calcs
natl_output_check_calcs: Inspector
File100000001 (writer CSV2_3)
    attributes: SurveyName string, SurveyId string, DHS_CountryCode string, SurveyYear string, SurveyType string, SurveyStatus string, CountryName string, SurveyYearLabel string, young_child_wt.nationalcount string, had_fever_wt.nationalcount string, public_treat_wt.nationalcount string, any_treat_wt.nationalcount string, had_fever_wt.nationalprop string, fever_public_treat_wt.nationalprop string, fever_any_treat_wt.nationalprop string, fever_public_treat_wt.nationalprop_LCI_GLM string, fever_public_treat_wt.nationalprop_UCI_GLM string, fever_any_treat_wt.nationalprop_LCI_GLM string, fever_any_treat_wt.nationalprop_UCI_GLM string, fever_public_treat_wt.nationalprop_LCI_SVY string, fever_public_treat_wt.nationalprop_UCI_SVY string, fever_any_treat_wt.nationalprop_LCI_SVY string, fever_any_treat_wt.nationalprop_UCI_SVY string, fever_any_treat_wt_clusterstderr string, fever_public_treat_wt_clusterstderr string, fever_any_treat_wt_clusterstdev string, fever_public_treat_wt_clusterstdev string, fever_any_treat_wt_clustermean string, fever_public_treat_wt_clustermean string
bob (writer CSV2_3)
    attributes: SurveyName string, SurveyId string, DHS_CountryCode string, SurveyYear string, SurveyType string, SurveyStatus string, CountryName string, SurveyYearLabel string, young_child_wt.nationalcount string, had_fever_wt.nationalcount string, public_treat_wt.nationalcount string, any_treat_wt.nationalcount string, had_fever_wt.nationalprop string, fever_public_treat_wt.nationalprop string, fever_any_treat_wt.nationalprop string, fever_public_treat_wt.nationalprop_LCI_CL string, fever_public_treat_wt.nationalprop_UCI_CL string, fever_any_treat_wt.nationalprop_LCI_CL string, fever_any_treat_wt.nationalprop_UCI_CL string, fever_public_treat_wt.nationalprop_LCI_GLM string, fever_public_treat_wt.nationalprop_UCI_GLM string, fever_any_treat_wt.nationalprop_LCI_GLM string, fever_any_treat_wt.nationalprop_UCI_GLM string, fever_public_treat_wt.nationalprop_LCI_SVY string, fever_public_treat_wt.nationalprop_UCI_SVY string, fever_any_treat_wt.nationalprop_LCI_SVY string, fever_any_treat_wt.nationalprop_UCI_SVY string, fever_any_treat_wt_clusterstderr string, fever_public_treat_wt_clusterstderr string, fever_any_treat_wt_clusterstdev string,
      fever_public_treat_wt_clusterstdev string, fever_any_treat_wt_clustermean string, fever_public_treat_wt_clustermean string
Missing_National_Svy_Info: Inspector

Bookmark: Estimate national CIs from cluster data
Note: Previously (in v1) confidence intervals for the national estimates were calculated by Kate. In v2 we have brought that calculation into the FME workflow. / We have also changed the methodology for calculating them as the old methodology was not suitable for the data.
